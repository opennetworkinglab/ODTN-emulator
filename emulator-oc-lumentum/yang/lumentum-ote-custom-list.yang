module lumentum-ote-custom-list {

  namespace "http://www.lumentum.com/lumentum-ote-custom-list";
  prefix "lotecl";

  organization "Lumentum Operations LLC";
  contact "support@lumentum.com";
  description
   "This module describes the operation and control for custom-list entities.
    A custom-list is intended to be used by the end-user to store key-value
    pairs of data of their own definition. The node does not do anything with 
    this information. It survives restarts and will be included in backup/
    restore operations.

    ---------------------------------------------------------------------------
    This document and its contents are proprietary and confidential to Lumentum
    Operations LLC, and/or its parent, subsidiary and/or affiliate entities.
    Neither this document, nor any part of it, may be disclosed or conveyed to,
    used or copied by or for, any third party without the prior written consent
    of Lumentum. LUMENTUM, and the LUMENTUM & DESIGN are trademarks of Lumentum
    Operations LLC. (c) 2017 Lumentum Operations LLC. All rights reserved. The
    use of a copyright notice on this document shall not be taken to indicate
    that it has been published.
    ---------------------------------------------------------------------------

   ";

  revision 2017-04-25 {
    description "Change element naming as follows: outer value to entry, custom-key to key.
    Minimum lengths of Custom-Key and Custom-Value changed from 0 to 1.
    Maximum lengths of Custom-Key and Custom-Value changed from 255 to 256.";
    reference "None";
  }

  revision 2017-02-27 {
    description "Initial revision.";
    reference "None";
  }

  /*
   * extension statements
   */

  /*
   * feature statements
   */

  /*
   * identity statements
   */

  /*
   * typedef statements
   */

  typedef Custom-Key {
    type string {
      length "1..256";
    }
    description
      "A user-specified key to be associated with a value.";
  }

  typedef Custom-Value {
    type string {
      length "1..256";
    }
    description
      "A user-specified value to be associated with a key.";
  }

  typedef Custom-List-Range {
    type uint8 {
      range "1..3";
    }
    description
      "The type used to identify the custom list.";
  }

  /*
   * grouping statements
   */

  grouping Custom-List-Key-Value-Pair {
    description
      "Defines the key-value pairs used in a custom list.";

    leaf key {
      type Custom-Key;
      description
        "The key for the custom-list.";
    }
    leaf value {
      type Custom-Value;
      description
        "The value for th custom-list.";
    }
  }

  grouping Custom-List-Top {
    container config {
        description "Configurable items of the custom-list.";
      list entry {
        key key;
        description
          "Each entry is a custom-value associated with a key.";
        uses Custom-List-Key-Value-Pair;
      }
    }

    description
      "Provides a definition for the top-level for a custom-list entity.";

  } // Custom-List-Top

  grouping Custom-List-Entities {
    description
      "Top level grouping for custom-list entities.";

    container custom-lists {
      list custom-list {
        key index;
        description
          "An entry for each custom-list.";

        leaf index {
          type Custom-List-Range;
          description
            "The index of the custom-list.";
        }

        uses Custom-List-Top;

      } // custom-list

      description
        "This provides top level container for the list of all custom-list
         entities.";
    }
  } // Custom-List-Entities


  /*
   * data definition statements
   */

  uses Custom-List-Entities;

  /*
   * augment statements
   */

  /*
   * rpc statements
   */

  /*
   * notification statements
   */
  
} // lumentum-ote-custom-list
